ETSISemanticsIdentifierMod { itu-t(0) identified-organization(4) etsi(0) id-certprofile(
194121) id-mod(0) id-mod-semantics-identifier(0) v2(1)}

DEFINITIONS EXPLICIT TAGS::=

BEGIN

id-etsi-qcs-semantics-identifiers OBJECT IDENTIFIER ::= { itu-t(0) identifiedorganization(4) etsi(0) id-cert-profile(194121) 1 }
-- Semantics identifier for natural person identifier
id-etsi-qcs-semanticsId-Natural OBJECT IDENTIFIER ::= { id-etsi-qcs-semanticsidentifiers
1 }
-- Semantics identifier for legal person identifier
id-etsi-qcs-SemanticsId-Legal OBJECT IDENTIFIER ::= { id-etsi-qcs-semanticsidentifiers
2 }
-- Semantics identifier for eIDAS natural person identifier
id-etsi-qcs-semanticsId-eIDASNatural OBJECT IDENTIFIER ::= { id-etsi-qcs-semantics-identifiers 3 }
-- Semantics identifier for legal person identifier
id-etsi-qcs-SemanticsId-eIDASLegal OBJECT IDENTIFIER ::= { id-etsi-qcs-semantics-identifiers 4 }

END
